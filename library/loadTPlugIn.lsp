;;---------------------
;; 关于“天正免费插件”
;;---------------------
;; ● 该插件是天正公司发布的免费插件，供没有安装天正发行版的用户使用，
;;    主要用于打印和阅读由天正建筑TArch、天正水、暖、电等绘制的图纸；
;; ● 该插件可以在天正官网下载: http://www.tangent.com.cn；
;; ● 该插件可运行于AutoCAD 2010-2022；
;; ● 安装有天正2010-2022系列相关专业软件的机器，不需要安装该插件；
;; ● 它提供了有限的几个功能，比如转换为天正低版本的图纸，供其他人使用；
;;
;; ● 当下载安装“天正免费插件”完毕，用户面板中的“天正面板(快捷键q7)”就会起作用


;;------------------
;; 天正插件启动程序
;;------------------
(if (and (<= 15 (fix (atof (getvar "ACADVER"))) 24)
         (setq tmpstr (findfile "tch_kernal.arx"))
    )
(progn
    (arxload tmpstr)
    (setq tmpstr nil)
)
)
