;;;=========================================================================
;;;         源 泉 设 计    用户自编LSP程序例子
;;;-------------------------------------------------------------------------
;;; 文件夹 sys\用户文件夹\
;;;
;;;     “用户文件夹”为自建文件夹。将自编或收集到的“.lsp/.vlx/.arx”程序
;;; 文件放入此文件夹下，再设定此“用户文件夹”为当前用户(用命令yq_setuser)，
;;; 则“源泉设计”在启动的时候会自动加载这些程序。
;;;=========================================================================
;;; 注：1. 此文件是用户自编LSP程序例子；
;;;     2. 代码行中分号";"后面是注释，行首加分号则暂时取消该行。



;;;========================
;;; 一些简单自定义命令例子
;;;========================

;;; 切换模型/布局
(defun c:1`()
  (setvar "TILEMODE" (if (= (getvar "TILEMODE") 0) 1 0))
)


;;; 切换图纸/模型空间
(defun c:``()
  (command (if (yq_ismodelspace) "PSPACE" "MSPACE"))
)

;;----- 新的语句可放在这里 -----







(princ)  ; 为最后一行
